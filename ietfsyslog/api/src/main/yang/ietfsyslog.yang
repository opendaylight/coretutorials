module ietfsyslog {
    yang-version 1;
    namespace "urn:opendaylight:params:xml:ns:yang:ietfsyslog";
    prefix "ietfsyslog";

    revision "2015-01-05" {
        description "Initial revision of ietfsyslog model";
    }
}
