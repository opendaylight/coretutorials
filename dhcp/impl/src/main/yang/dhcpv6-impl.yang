module dhcpv6-impl {
    yang-version 1;
    namespace "urn:opendaylight:params:xml:ns:yang:dhcp:impl:v6";
    prefix "dhcpv6-impl";

    import config { prefix config; revision-date 2013-04-05; }
    import ietf-inet-types { prefix inet; }
    import opendaylight-md-sal-binding { prefix md-sal-binding; revision-date 2013-10-28; }
    import netty { prefix netty; }

    description
        "Service definition for dhcpv6 project";

    revision "2015-10-18" {
        description
            "Initial revision";
    }

    identity dhcpv6-lease-manager {
        base "config:service-type";
        config:java-class "org.anarres.dhcp.v6.service.Dhcp6LeaseManager";
    }

    identity examplev6-lease-manager {
        base config:module-type;
        config:provided-service dhcpv6-lease-manager;
    }

    augment "/config:modules/config:module/config:configuration" {
        case examplev6-lease-manager {
            when "/config:modules/config:module/config:type = 'examplev6-lease-manager'";

            leaf ip {
                type string;
                description "Ip to lease to every client";
            }
        }
    }

    typedef message-type {
        type enumeration {
            enum "DHCPADVERTISE" {
                value 3;
                description "DHCPv6 Advertise";
            }
            enum "DHCPREPLY" {
                value 5;
                description "DHCPv6 Reply";
             }
             enum "ALL" {
                 value 9;
                 description "all DHCPv6 messages";
             }
         }
     }


    identity dhcpv6 {
        base config:module-type;
        config:java-name-prefix Dhcpv6;
    }

     augment "/config:modules/config:module/config:configuration" {
            case dhcpv6 {
                when "/config:modules/config:module/config:type = 'dhcpv6'";

                container worker-thread-group {
                    uses config:service-ref {
                        refine type {
                            config:required-identity netty:netty-threadgroup;
                        }
                    }
                }

                leaf port {
                    type inet:port-number;
                    description "port to bind the DHCPv6 server to";
                    default 547;
                }

                leaf-list network-interface {
                    description "network interfaces upon the dhcp server should listen to";
                    type string;
                }

                list default-option {
                    description "options which will be included in the chosen outcoming DHCP message";
                    key "id scope";
                    leaf id {
                        type uint16;
                    }
                    leaf value {
                        type string;
                    }
                    leaf scope {
                       type message-type;
                    }
                }

                leaf server-id {
                    description "dhcp server handler id";
                    type uint16;
                }

                container lease-manager {
                uses config:service-ref {
                    refine type {
                        config:required-identity dhcpv6-lease-manager;
                    }
                }
            }
            }
    }

}
