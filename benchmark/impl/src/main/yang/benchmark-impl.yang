module benchmark-impl {
    yang-version 1;
    namespace "urn:opendaylight:params:xml:ns:yang:benchmark:impl";
    prefix "benchmark-impl";

    import config { prefix config; revision-date 2013-04-05; }
    import opendaylight-md-sal-binding { prefix md-sal-binding; revision-date 2013-10-28;}

    description
        "Service definition for benchmark project";

    revision "2014-12-10" {
        description
            "Initial revision";
    }

    identity benchmark {
        base config:module-type;
        config:java-name-prefix Benchmark;
    }

    augment "/config:modules/config:module/config:configuration" {
        case benchmark {
            when "/config:modules/config:module/config:type = 'benchmark'";
            container broker {
                uses config:service-ref {
                    refine type {
                        mandatory true;
                        config:required-identity md-sal-binding:binding-broker-osgi-registry;
                    }
                }
            }
        }
    }
}
