module clustering-routed-rpc {
    yang-version 1;
    namespace "urn:opendaylight:params:xml:ns:yang:clustering:routed:rpc";
    prefix "rrpc";

    import yang-ext { prefix ext; revision-date 2013-07-09; }
    import clustering { prefix clst; revision-date 2016-07-22; }

    revision "2016-07-22" {
        description "Initial revision of global-rpc example model";
    }

    identity routed-rpc-context {
        description "Test Routed RPC Context";
    }

    list rpc-member {
        config false;
        leaf name {
            type string;
            description
                "";
        }
        key "name";
    }

    rpc routed-rpc {
        description
            "Definition of an example routed RPC in the clustering Singleton
            Project. The Clustering Singleton Service determines a Leader node
            for the service and a routed RPC service instance is instantiated
            on the Leader. The is a single instance of the routed RPC service
            running on the Leader. When the Leader moves to a different node,
            the current instance is shut down and a new instance is created on
            the new Leader.";

        input {
            leaf route {
                type instance-identifier;
                ext:context-reference routed-rpc-context;
                description
                    'Identifies the RPC instance to which the RPC call
                    should be routed. The instance identifier for the routed
                    RPC in this example must in the following format:
                    /clustering-routed-rpc:rpc-member[clustering-routed-rpc:name="rpc-key"]';
            }

            uses clst:rpc-input;
        }

        output {
            uses clst:rpc-output;
        }
    }
}
