module clustering {
    yang-version 1;
    namespace "urn:opendaylight:params:xml:ns:yang:clustering";
    prefix "grpc";

    import ietf-inet-types { prefix inet; }

    revision "2016-07-22" {
        description "Initial revision of global-rpc example model";
    }

    grouping rpc-output {
        leaf output-param {
            type string;
            description
                "Output parameter (mirros the input parameter entered
                by the user";
        }

        leaf invocations {
            type int32;
            description
                "Service invocation counter; incremented each time
                the service is invoked.";
        }

        leaf host-name {
            type string;
            description
                "Hostname of the host where the JVM runs";
        }

        leaf jvm-uptime {
            type int64;
            description
                "The time (in ms) for how long the JVM was up";
        }

        leaf-list ip-address {
            type string;
            description
                "List of IP addresses on all interfaces of the host
                where the JVM runs";
        }
    }

    rpc global-rpc {
        input {
            leaf input-param {
                type string;
                description
                    "Input parameter (optional)";
            }
        }
        output {
            uses rpc-output;
        }
    }

    rpc routed-rpc {
        input {
            leaf input-param {
                type string;
                description
                    "Input parameter (optional)";
            }
        }
        output {
            uses rpc-output;
        }
    }

}
