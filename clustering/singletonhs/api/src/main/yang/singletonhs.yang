module singletonhs {
    yang-version 1;
    namespace "urn:opendaylight:params:xml:ns:yang:singletonhs";
    prefix "singletonhs";

    revision "2015-01-05" {
        description "Initial revision of singletonhs model";
    }
}
