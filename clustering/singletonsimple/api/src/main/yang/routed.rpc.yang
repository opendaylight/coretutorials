module routed-rpc {
    yang-version 1;
    namespace "urn:opendaylight:params:xml:ns:yang:clustering:singleton:simple:routed:rpc";
    prefix "rrpc";

    import yang-ext { prefix ext; }
    import commons { prefix cmns; revision-date 2016-07-22; }

    revision "2016-07-22" {
        description "Initial revision of global-rpc example model";
    }

    identity routed-rpc-context {
        description "Test Routed RPC Context";
    }

    list rpc-member {
        config false;
        leaf name {
            type string;
            description
                "";
        }
        key "name";
    }

    rpc routed-rpc {
        description
            "Definition of an example routed RPC in the clustering Singleton
            Project. The Clustering Singleton Service determines a Leader node
            for the service and a routed RPC service instance is instantiated
            on the Leader. The is a single instance of the routed RPC service
            running on the Leader. When the Leader moves to a different node,
            the current instance is shut down and a new instance is created on
            the new Leader.";

        input {
            leaf route {
                type instance-identifier;
                ext:context-reference routed-rpc-context;
                description
                    'Identifies the RPC instance to which the RPC call
                    should be routed. The instance identifier for the routed
                    RPC in this example must in the following format:
                    /routed-rpc:rpc-member[routed-rpc:name="rpc-key"]';
            }

            uses cmns:rpc-input;
        }

        output {
            uses cmns:rpc-output;
        }
    }
}
