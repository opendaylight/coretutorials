// Contents of "singleton-app-global-rpc"
module singleton-app-global-rpc {
    yang-version 1;
    namespace "urn:opendaylight:params:xml:ns:yang:coretutorials:singleton-app-global-rpc";
    prefix "singleton-app-global-rpc";

    import clustering-rpc-common { prefix rpc-common; revision-date 2016-07-22; }

    revision "2016-07-22" {
        description "Initial revision of global-rpc example model";
    }

    rpc global-singleton-app-rpc {
        description
            "Definition of an example global RPC in the clustering Singleton
            Project. The Clustering Singleton Service determines a Leader node
            for the service and a global RPC service instance is instantiated
            on the Leader. The is a single instance of the global RPC service
            running on the Leader. When the Leader moves to a different node,
            the current instance is shut down and a new instance is created on
            the new Leader. Invocation of this service on a Follower node will
            fail";

        input {
            uses rpc-common:rpc-input;
        }

        output {
            uses rpc-common:rpc-output;
        }
    }
}
