module clustering-local-rpc {
    yang-version 1;
    namespace "urn:opendaylight:params:xml:ns:yang:clustering:local:rpc";
    prefix "clst";

    import clustering { prefix lclst; }

    revision "2016-07-22" {
        description "Initial revision of global-rpc example model";
    }

    rpc local-rpc {
        description
            "Definition of a 'node-local' RPC. There is one RPC instance
            registered with MD-SAL for each node in the cluster.";

        input {
            uses lclst:rpc-input;
        }

        output {
            uses lclst:rpc-output;
        }
    }
}
