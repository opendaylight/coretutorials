module toaster-impl-config {
    yang-version 1;
    namespace "urn:opendaylight:params:xml:ns:yang:toaster:impl:config";
    prefix "toaster-impl-config";

    import config { prefix config; revision-date 2013-04-05; }
    import opendaylight-md-sal-binding { prefix md-sal-binding; revision-date 2013-10-28;}
    import rpc-context { prefix rpcx; revision-date 2013-06-17; }

    description
        "Service definition for toaster project";

    revision "2014-12-10" {
        description
            "Initial revision";
    }

    identity toaster-impl-config {
        base config:module-type;
        config:java-name-prefix ToasterImpl;
    }

    augment "/config:modules/config:module/config:configuration" {
        case toaster-impl-config {
            when "/config:modules/config:module/config:type = 'toaster-impl-config'";
            container binding-aware-broker {
                uses config:service-ref {
                    refine type {
                        mandatory true;
                        config:required-identity md-sal-binding:binding-broker-osgi-registry;
                    }
                }
            }
        }
    }

    // adding jmx/jconsole access to internal toaster state
    augment "/config:modules/config:module/config:state" {
        case toaster-impl-config {
            when "/config:modules/config:module/config:type = 'toaster-impl-config'";

            leaf toasts-made {
                type uint32;
            }

            rpcx:rpc-context-instance "clear-toasts-made-rpc";
        }
    }

    identity clear-toasts-made-rpc;

    rpc clear-toasts-made  {
        description
          "JMX call to clear the toasts-made counter.";

        input {
            uses rpcx:rpc-context-ref {
                refine context-instance {
                    rpcx:rpc-context-instance clear-toasts-made-rpc;
                }
            }
        }
    }
}
