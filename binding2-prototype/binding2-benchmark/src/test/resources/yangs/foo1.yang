module foo1{
    namespace "urn:test:foo1";
    prefix foo1;

    revision 2017-01-01;

    grouping A {
           container A1 {
                container A1-inner {
                            leaf leaf-A1-inner{
                                type string;

                            }
                            container A1-inner-inner {
                                leaf leaf-A1-inner-inner{
                                    type string;

                                }
                            }
                       }
           }
        }

    grouping B {
           container B1 {
                container B1-inner {
                            leaf leaf-B1-inner{
                                type string;

                            }
                            container B1-inner-inner {
                                leaf leaf-B1-inner-inner{
                                    type string;

                                }
                            }
                       }
           }
        }

     grouping C {
            container C1 {
                 container C1-inner {
                             leaf leaf-C1-inner{
                                 type string;

                             }
                             container C1-inner-inner {
                                 leaf leaf-C1-inner-inner{
                                     type string;

                                 }
                             }
                        }
            }
         }

    grouping E {
                container E1 {
                     container E1-inner {
                                 leaf leaf-E1-inner{
                                     type string;

                                 }
                                 container E1-inner-inner {
                                     leaf leaf-E1-inner-inner{
                                         type string;

                                     }
                                 }
                            }
                }
             }

}
