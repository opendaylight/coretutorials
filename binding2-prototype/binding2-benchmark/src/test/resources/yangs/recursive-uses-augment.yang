module recursive-uses-augment {

    namespace "yang:test:uses-augment-recursive";
    prefix ruses;

    revision 2017-05-19;

    container my-cont {
      uses D;
    }
    
    grouping A {
        container A1 {
            leaf leaf-A1 {
                type string;
            }
        }
    }

    grouping B {
        container B1 {
            leaf leaf-B1 {
                type string;
            }
        }
    }

    grouping C {
        container C1 {
            leaf leaf-C1 {
                type string;
            }
        }
    }

    grouping D {
        uses "A" {
            augment "A1" {
                uses B {
                    augment "B1" {
                        uses C {
                            augment  "C1" {
                                leaf D-aug-C1 {
                                    type string;
                                }
                            }
                        }
                    }
                }
            }
        }
    }
}
