module test-import {
    yang-version 1;

    namespace "urn:test:simple:test:import";
    prefix test-import;
    organization "test.import.org";
    revision "2017-04-21";

    container *my-import-%cont {
    }
}
