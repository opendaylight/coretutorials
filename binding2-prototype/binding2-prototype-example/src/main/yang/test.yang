module test {
    yang-version 1;

    namespace "urn:test:simple:test";
    prefix test;
    organization "test.org";
    revision "2017-02-06";

    import test-import {
      prefix "imported-test";
    }

    typedef my-type {
      type int8;
    }

    container *my-cont {
      container my-inner-cont {
        leaf my-leaf {
          type string;
        }
      }
    }

    grouping my-grouping {
      container *my-cont {
      }
    }
}
