module rpc-test {
    namespace rpc-test-namespace;
    prefix rpc-test-prefix;

    revision 2017-04-25;

    rpc foo-rpc-1 {
        input {
            leaf foo-leaf-1 {
                type string;
            }
        }

        output {
            leaf foo-leaf-2 {
                type string;
            }
        }
    }
}
