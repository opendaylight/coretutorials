module binding2-prototype-orig {
    yang-version 1;
    namespace "urn:opendaylight:params:xml:ns:yang:binding2-prototype:original";
    prefix "bind2prot";

    revision "2017-05-05" {
        description "Initial revision of binding2-prototype model";
    }

//    rpc hello-world {
//        input {
//            leaf name {
//                type string;
//            }
//        }
//        output {
//            leaf greeting {
//                type string;
//            }
//        }
//    }
    container cont-test{
        leaf leaf-test{
            type string;
        }
    }
}
