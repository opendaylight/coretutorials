module binding2-prototype-app-impl {
    yang-version 1;
    namespace "urn:opendaylight:params:xml:ns:yang:binding2-prototype-app-impl";
    prefix "binding2-prototype-app-impl";

    import config { prefix config; revision-date 2013-04-05; }
    import opendaylight-md-sal-binding { prefix md-sal-binding; revision-date 2013-10-28;}
    import opendaylight-md-sal-dom { prefix md-sal-dom; revision-date 2013-10-28;}

    description
        "Service definition for binding2-prototype-app project";

    revision "2017-05-05" {
        description
            "Initial revision";
    }

    identity binding2-prototype-app-impl {
        base config:module-type;
        config:java-name-prefix Binding2PrototypeApp;
    }

    augment "/config:modules/config:module/config:configuration" {
        case binding2-prototype-app-impl {
            when "/config:modules/config:module/config:type = 'binding2-prototype-app-impl'";
            container broker {
                uses config:service-ref {
                    refine type {
                        mandatory true;
                        config:required-identity md-sal-binding:binding-broker-osgi-registry;
                    }
                }
            }
            container dom-data-broker {
                uses config:service-ref {
                    refine type {
                        mandatory true;
                        config:required-identity md-sal-dom:dom-async-data-broker;
                    }
                }
            }
            container binding-data-broker {
                uses config:service-ref {
                    refine type {
                        mandatory true;
                        config:required-identity md-sal-binding:binding-async-data-broker;
                    }
                }
            }
        }
    }
}
