module binding1-example-app {
    yang-version 1;
    namespace "urn:opendaylight:params:xml:ns:yang:binding1-example-app";
    prefix "bind2prot";

    revision "2017-05-05" {
        description "Initial revision of binding1-example-app model";
    }

    rpc hello-world-binding1 {
        input {
            leaf name-binding1 {
                type string;
            }
        }
        output {
            leaf greeting-binding1 {
                type string;
            }
        }
    }

    container cont-test-binding1{
        leaf leaf-test-binding1{
            type string;
        }
    }
}
