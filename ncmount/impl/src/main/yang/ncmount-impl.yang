module ncmount-impl {
    yang-version 1;
    namespace "urn:opendaylight:params:xml:ns:yang:ncmount:impl";
    prefix "ncmount-impl";

    import config { prefix config; revision-date 2013-04-05; }
    import opendaylight-md-sal-binding { prefix md-sal-binding; revision-date 2013-10-28;}
    import opendaylight-md-sal-dom {prefix dom;}

    description
        "Service definition for ncmount project";

    revision "2014-12-10" {
        description
            "Initial revision";
    }

    identity ncmount {
        base config:module-type;
        config:java-name-prefix Ncmount;
    }

    // We need only one broker at a time (BA/ BI broker).
    // Depending on the provider implementation BA or BI, 
    // thats created inside the Module.
    augment "/config:modules/config:module/config:configuration" {
        case ncmount {
            when "/config:modules/config:module/config:type = 'ncmount'";

            // BA broker
            container broker {
                uses config:service-ref {
                    refine type {
                        mandatory true;
                        config:required-identity md-sal-binding:binding-broker-osgi-registry;
                    }
                }
            }

            // BI broker
            container dom-broker {
                uses config:service-ref {
                    refine type {
                        mandatory true;
                        config:required-identity dom:dom-broker-osgi-registry;
                    }
                }
            }
        }
    }
}
