module ncmount {
    yang-version 1;
    namespace "urn:opendaylight:params:xml:ns:yang:ncmount";
    prefix "ncmount";

    revision "2015-01-05" {
        description "Initial revision of ncmount model";
    }

    rpc show-node {
        description
          "Start a new data store write test run";

        input {
            leaf node-name {
                mandatory true;
                type string;
                description
                    "Name of the mounted node to be displayed";
            }
        }
        output {
            leaf interfaces {
                type uint32;
                description
                  "Number of interfaces on the node. Just a mock today";
              }

        }
    }

}
